[DOCUMENT]
TITLE: Local harness evidence and its limits
UID: OAK-HARNESS
VERSION: 0.4.1

[GRAMMAR]
IMPORT_FROM_FILE: oak.sgra

[TEST]
UID: H-T01
STATUS: PassedSubstitute
OWNER: Integration
SOURCE: tests/oak_contracts/test_contracts.py::test_cross_project_same_ids_do_not_grant_access
SCOPE: EngineeringHarness
VERIFICATION: PassedSubstitute
TITLE: test_cross_project_same_ids_do_not_grant_access
STATEMENT: >>>
The recorded local harness executed test_cross_project_same_ids_do_not_grant_access and returned passed. The receipt pins the tested source hashes. This is a narrower substitute test, not the related production service test.
<<<
RELATIONS:
- TYPE: Parent
  VALUE: C9-R02
  ROLE: Exercises
- TYPE: Parent
  VALUE: C9-R03
  ROLE: Exercises

[TEST]
UID: H-T02
STATUS: PassedSubstitute
OWNER: Integration
SOURCE: tests/oak_contracts/test_contracts.py::test_hash_knowledge_does_not_grant_artifact_access
SCOPE: EngineeringHarness
VERIFICATION: PassedSubstitute
TITLE: test_hash_knowledge_does_not_grant_artifact_access
STATEMENT: >>>
The recorded local harness executed test_hash_knowledge_does_not_grant_artifact_access and returned passed. The receipt pins the tested source hashes. This is a narrower substitute test, not the related production service test.
<<<
RELATIONS:
- TYPE: Parent
  VALUE: C9-R02
  ROLE: Exercises

[TEST]
UID: H-T03
STATUS: PassedSubstitute
OWNER: Integration
SOURCE: tests/oak_contracts/test_contracts.py::test_artifact_bytes_and_kind_are_verified
SCOPE: EngineeringHarness
VERIFICATION: PassedSubstitute
TITLE: test_artifact_bytes_and_kind_are_verified
STATEMENT: >>>
The recorded local harness executed test_artifact_bytes_and_kind_are_verified and returned passed. The receipt pins the tested source hashes. This is a narrower substitute test, not the related production service test.
<<<
RELATIONS:
- TYPE: Parent
  VALUE: C0-R08
  ROLE: Exercises
- TYPE: Parent
  VALUE: C10-R07
  ROLE: Exercises

[TEST]
UID: H-T04
STATUS: PassedSubstitute
OWNER: Integration
SOURCE: tests/oak_contracts/test_contracts.py::test_contracts_reject_unknown_fields_and_schema_mismatch
SCOPE: EngineeringHarness
VERIFICATION: PassedSubstitute
TITLE: test_contracts_reject_unknown_fields_and_schema_mismatch
STATEMENT: >>>
The recorded local harness executed test_contracts_reject_unknown_fields_and_schema_mismatch and returned passed. The receipt pins the tested source hashes. This is a narrower substitute test, not the related production service test.
<<<
RELATIONS:
- TYPE: Parent
  VALUE: CT-SHARED
  ROLE: Exercises

[TEST]
UID: H-T05
STATUS: PassedSubstitute
OWNER: Integration
SOURCE: tests/oak_contracts/test_contracts.py::test_user_cannot_issue_verifier_receipts
SCOPE: EngineeringHarness
VERIFICATION: PassedSubstitute
TITLE: test_user_cannot_issue_verifier_receipts
STATEMENT: >>>
The recorded local harness executed test_user_cannot_issue_verifier_receipts and returned passed. The receipt pins the tested source hashes. This is a narrower substitute test, not the related production service test.
<<<
RELATIONS:
- TYPE: Parent
  VALUE: C9-R05
  ROLE: Exercises
- TYPE: Parent
  VALUE: C10-R06
  ROLE: Exercises

[TEST]
UID: H-T06
STATUS: PassedSubstitute
OWNER: Integration
SOURCE: tests/oak_contracts/test_contracts.py::test_failed_or_unrun_layer_blocks_activation[failed]
SCOPE: EngineeringHarness
VERIFICATION: PassedSubstitute
TITLE: test_failed_or_unrun_layer_blocks_activation[failed]
STATEMENT: >>>
The recorded local harness executed test_failed_or_unrun_layer_blocks_activation[failed] and returned passed. The receipt pins the tested source hashes. This is a narrower substitute test, not the related production service test.
<<<
RELATIONS:
- TYPE: Parent
  VALUE: SYS-R04
  ROLE: Exercises

[TEST]
UID: H-T07
STATUS: PassedSubstitute
OWNER: Integration
SOURCE: tests/oak_contracts/test_contracts.py::test_failed_or_unrun_layer_blocks_activation[not_run]
SCOPE: EngineeringHarness
VERIFICATION: PassedSubstitute
TITLE: test_failed_or_unrun_layer_blocks_activation[not_run]
STATEMENT: >>>
The recorded local harness executed test_failed_or_unrun_layer_blocks_activation[not_run] and returned passed. The receipt pins the tested source hashes. This is a narrower substitute test, not the related production service test.
<<<
RELATIONS:
- TYPE: Parent
  VALUE: SYS-R04
  ROLE: Exercises

[TEST]
UID: H-T08
STATUS: PassedSubstitute
OWNER: Integration
SOURCE: tests/oak_contracts/test_contracts.py::test_failed_or_unrun_layer_blocks_activation[error]
SCOPE: EngineeringHarness
VERIFICATION: PassedSubstitute
TITLE: test_failed_or_unrun_layer_blocks_activation[error]
STATEMENT: >>>
The recorded local harness executed test_failed_or_unrun_layer_blocks_activation[error] and returned passed. The receipt pins the tested source hashes. This is a narrower substitute test, not the related production service test.
<<<
RELATIONS:
- TYPE: Parent
  VALUE: SYS-R04
  ROLE: Exercises

[TEST]
UID: H-T09
STATUS: PassedSubstitute
OWNER: Integration
SOURCE: tests/oak_contracts/test_contracts.py::test_report_missing_gate_or_changed_test_inputs_blocks_activation
SCOPE: EngineeringHarness
VERIFICATION: PassedSubstitute
TITLE: test_report_missing_gate_or_changed_test_inputs_blocks_activation
STATEMENT: >>>
The recorded local harness executed test_report_missing_gate_or_changed_test_inputs_blocks_activation and returned passed. The receipt pins the tested source hashes. This is a narrower substitute test, not the related production service test.
<<<
RELATIONS:
- TYPE: Parent
  VALUE: CT-GATES
  ROLE: Exercises

[TEST]
UID: H-T10
STATUS: PassedSubstitute
OWNER: Integration
SOURCE: tests/oak_contracts/test_contracts.py::test_tampered_report_cannot_activate
SCOPE: EngineeringHarness
VERIFICATION: PassedSubstitute
TITLE: test_tampered_report_cannot_activate
STATEMENT: >>>
The recorded local harness executed test_tampered_report_cannot_activate and returned passed. The receipt pins the tested source hashes. This is a narrower substitute test, not the related production service test.
<<<
RELATIONS:
- TYPE: Parent
  VALUE: CT-GATES
  ROLE: Exercises

[TEST]
UID: H-T11
STATUS: PassedSubstitute
OWNER: Integration
SOURCE: tests/oak_contracts/test_contracts.py::test_stale_activation_and_candidate_report_mismatch
SCOPE: EngineeringHarness
VERIFICATION: PassedSubstitute
TITLE: test_stale_activation_and_candidate_report_mismatch
STATEMENT: >>>
The recorded local harness executed test_stale_activation_and_candidate_report_mismatch and returned passed. The receipt pins the tested source hashes. This is a narrower substitute test, not the related production service test.
<<<
RELATIONS:
- TYPE: Parent
  VALUE: CT-GATES
  ROLE: Exercises

[TEST]
UID: H-T12
STATUS: PassedSubstitute
OWNER: Integration
SOURCE: tests/oak_contracts/test_contracts.py::test_active_run_keeps_package_after_activation
SCOPE: EngineeringHarness
VERIFICATION: PassedSubstitute
TITLE: test_active_run_keeps_package_after_activation
STATEMENT: >>>
The recorded local harness executed test_active_run_keeps_package_after_activation and returned passed. The receipt pins the tested source hashes. This is a narrower substitute test, not the related production service test.
<<<
RELATIONS:
- TYPE: Parent
  VALUE: SYS-R03
  ROLE: Exercises
- TYPE: Parent
  VALUE: C4-R07
  ROLE: Exercises

[TEST]
UID: H-T13
STATUS: PassedSubstitute
OWNER: Integration
SOURCE: tests/oak_contracts/test_contracts.py::test_lost_ack_replay_after_reopen_has_one_revision
SCOPE: EngineeringHarness
VERIFICATION: PassedSubstitute
TITLE: test_lost_ack_replay_after_reopen_has_one_revision
STATEMENT: >>>
The recorded local harness executed test_lost_ack_replay_after_reopen_has_one_revision and returned passed. The receipt pins the tested source hashes. This is a narrower substitute test, not the related production service test.
<<<
RELATIONS:
- TYPE: Parent
  VALUE: C2-R05
  ROLE: Exercises
- TYPE: Parent
  VALUE: C2-R07
  ROLE: Exercises

[TEST]
UID: H-T14
STATUS: PassedSubstitute
OWNER: Integration
SOURCE: tests/oak_contracts/test_contracts.py::test_changed_observation_identity_is_rejected_without_write
SCOPE: EngineeringHarness
VERIFICATION: PassedSubstitute
TITLE: test_changed_observation_identity_is_rejected_without_write
STATEMENT: >>>
The recorded local harness executed test_changed_observation_identity_is_rejected_without_write and returned passed. The receipt pins the tested source hashes. This is a narrower substitute test, not the related production service test.
<<<
RELATIONS:
- TYPE: Parent
  VALUE: C2-R02
  ROLE: Exercises

[TEST]
UID: H-T15
STATUS: PassedSubstitute
OWNER: Integration
SOURCE: tests/oak_contracts/test_contracts.py::test_concurrent_commits_have_one_winner_at_parent
SCOPE: EngineeringHarness
VERIFICATION: PassedSubstitute
TITLE: test_concurrent_commits_have_one_winner_at_parent
STATEMENT: >>>
The recorded local harness executed test_concurrent_commits_have_one_winner_at_parent and returned passed. The receipt pins the tested source hashes. This is a narrower substitute test, not the related production service test.
<<<
RELATIONS:
- TYPE: Parent
  VALUE: C2-R05
  ROLE: Exercises

[TEST]
UID: H-T16
STATUS: PassedSubstitute
OWNER: Integration
SOURCE: tests/oak_contracts/test_contracts.py::test_required_evidence_and_stable_revision
SCOPE: EngineeringHarness
VERIFICATION: PassedSubstitute
TITLE: test_required_evidence_and_stable_revision
STATEMENT: >>>
The recorded local harness executed test_required_evidence_and_stable_revision and returned passed. The receipt pins the tested source hashes. This is a narrower substitute test, not the related production service test.
<<<
RELATIONS:
- TYPE: Parent
  VALUE: C2-R06
  ROLE: Exercises
- TYPE: Parent
  VALUE: C2-R09
  ROLE: Exercises
- TYPE: Parent
  VALUE: C3-R03
  ROLE: Exercises

[TEST]
UID: H-T17
STATUS: PassedSubstitute
OWNER: Integration
SOURCE: tests/oak_contracts/test_contracts.py::test_unknown_conflict_and_false_remain_distinct
SCOPE: EngineeringHarness
VERIFICATION: PassedSubstitute
TITLE: test_unknown_conflict_and_false_remain_distinct
STATEMENT: >>>
The recorded local harness executed test_unknown_conflict_and_false_remain_distinct and returned passed. The receipt pins the tested source hashes. This is a narrower substitute test, not the related production service test.
<<<
RELATIONS:
- TYPE: Parent
  VALUE: C2-R04
  ROLE: Exercises
- TYPE: Parent
  VALUE: C3-R02
  ROLE: Exercises

[TEST]
UID: H-T18
STATUS: PassedSubstitute
OWNER: Integration
SOURCE: tests/oak_contracts/test_contracts.py::test_wrong_request_scope_and_bad_type_leave_no_projection
SCOPE: EngineeringHarness
VERIFICATION: PassedSubstitute
TITLE: test_wrong_request_scope_and_bad_type_leave_no_projection
STATEMENT: >>>
The recorded local harness executed test_wrong_request_scope_and_bad_type_leave_no_projection and returned passed. The receipt pins the tested source hashes. This is a narrower substitute test, not the related production service test.
<<<
RELATIONS:
- TYPE: Parent
  VALUE: C2-R01
  ROLE: Exercises
- TYPE: Parent
  VALUE: C2-R04
  ROLE: Exercises

[TEST]
UID: H-T19
STATUS: PassedSubstitute
OWNER: Integration
SOURCE: tests/oak_contracts/test_contracts.py::test_stale_source_and_mixed_package_view_are_rejected
SCOPE: EngineeringHarness
VERIFICATION: PassedSubstitute
TITLE: test_stale_source_and_mixed_package_view_are_rejected
STATEMENT: >>>
The recorded local harness executed test_stale_source_and_mixed_package_view_are_rejected and returned passed. The receipt pins the tested source hashes. This is a narrower substitute test, not the related production service test.
<<<
RELATIONS:
- TYPE: Parent
  VALUE: CT-C7
  ROLE: Exercises

[TEST]
UID: H-T20
STATUS: PassedSubstitute
OWNER: Integration
SOURCE: tests/oak_contracts/test_contracts.py::test_budget_reservations_survive_reopen_and_completion_redelivery
SCOPE: EngineeringHarness
VERIFICATION: PassedSubstitute
TITLE: test_budget_reservations_survive_reopen_and_completion_redelivery
STATEMENT: >>>
The recorded local harness executed test_budget_reservations_survive_reopen_and_completion_redelivery and returned passed. The receipt pins the tested source hashes. This is a narrower substitute test, not the related production service test.
<<<
RELATIONS:
- TYPE: Parent
  VALUE: C10-R08
  ROLE: Exercises
- TYPE: Parent
  VALUE: C4-R03
  ROLE: Exercises

[TEST]
UID: H-T21
STATUS: PassedSubstitute
OWNER: Integration
SOURCE: tests/oak_contracts/test_contracts.py::test_deadline_and_operation_collision_do_not_create_calls
SCOPE: EngineeringHarness
VERIFICATION: PassedSubstitute
TITLE: test_deadline_and_operation_collision_do_not_create_calls
STATEMENT: >>>
The recorded local harness executed test_deadline_and_operation_collision_do_not_create_calls and returned passed. The receipt pins the tested source hashes. This is a narrower substitute test, not the related production service test.
<<<
RELATIONS:
- TYPE: Parent
  VALUE: C10-R08
  ROLE: Exercises

[TEST]
UID: H-T22
STATUS: PassedSubstitute
OWNER: Integration
SOURCE: tests/oak_contracts/test_contracts.py::test_schema_repair_invalidates_dependents_and_rejects_stale_or_held_out
SCOPE: EngineeringHarness
VERIFICATION: PassedSubstitute
TITLE: test_schema_repair_invalidates_dependents_and_rejects_stale_or_held_out
STATEMENT: >>>
The recorded local harness executed test_schema_repair_invalidates_dependents_and_rejects_stale_or_held_out and returned passed. The receipt pins the tested source hashes. This is a narrower substitute test, not the related production service test.
<<<
RELATIONS:
- TYPE: Parent
  VALUE: SYS-R04
  ROLE: Exercises
- TYPE: Parent
  VALUE: C5-R06
  ROLE: Exercises
- TYPE: Parent
  VALUE: C5-R08
  ROLE: Exercises

[TEST]
UID: H-T23
STATUS: PassedSubstitute
OWNER: Integration
SOURCE: tests/oak_contracts/test_contracts.py::test_evaluator_rejects_wrong_result_despite_local_success
SCOPE: EngineeringHarness
VERIFICATION: PassedSubstitute
TITLE: test_evaluator_rejects_wrong_result_despite_local_success
STATEMENT: >>>
The recorded local harness executed test_evaluator_rejects_wrong_result_despite_local_success and returned passed. The receipt pins the tested source hashes. This is a narrower substitute test, not the related production service test.
<<<
RELATIONS:
- TYPE: Parent
  VALUE: C5-R03
  ROLE: Exercises

[TEST]
UID: H-T24
STATUS: PassedSubstitute
OWNER: Integration
SOURCE: tests/oak_contracts/test_contracts.py::test_evaluator_preserves_denominator_and_rejects_duplicate
SCOPE: EngineeringHarness
VERIFICATION: PassedSubstitute
TITLE: test_evaluator_preserves_denominator_and_rejects_duplicate
STATEMENT: >>>
The recorded local harness executed test_evaluator_preserves_denominator_and_rejects_duplicate and returned passed. The receipt pins the tested source hashes. This is a narrower substitute test, not the related production service test.
<<<
RELATIONS:
- TYPE: Parent
  VALUE: C5-R01
  ROLE: Exercises
- TYPE: Parent
  VALUE: C5-R02
  ROLE: Exercises

[EVIDENCE]
UID: EV-HARNESS-20261102-201512
STATUS: Recorded
OWNER: Integration
SOURCE: .runtime/oak-contracts/20261102T201512Z-a8875ae3/receipt.json
SCOPE: EngineeringHarness
VERIFICATION: NotApplicable
TITLE: Offline harness receipt
STATEMENT: >>>
This receipt records 24 assigned checks and 24 passing local substitute outcomes. It uses SQLite and saved synthetic inputs. It does not run OIDC, PostgreSQL, Neo4j, HermiT, the production host, or a model.
<<<
RELATIONS:
- TYPE: Parent
  VALUE: H-T01
  ROLE: Supports
- TYPE: Parent
  VALUE: H-T02
  ROLE: Supports
- TYPE: Parent
  VALUE: H-T03
  ROLE: Supports
- TYPE: Parent
  VALUE: H-T04
  ROLE: Supports
- TYPE: Parent
  VALUE: H-T05
  ROLE: Supports
- TYPE: Parent
  VALUE: H-T06
  ROLE: Supports
- TYPE: Parent
  VALUE: H-T07
  ROLE: Supports
- TYPE: Parent
  VALUE: H-T08
  ROLE: Supports
- TYPE: Parent
  VALUE: H-T09
  ROLE: Supports
- TYPE: Parent
  VALUE: H-T10
  ROLE: Supports
- TYPE: Parent
  VALUE: H-T11
  ROLE: Supports
- TYPE: Parent
  VALUE: H-T12
  ROLE: Supports
- TYPE: Parent
  VALUE: H-T13
  ROLE: Supports
- TYPE: Parent
  VALUE: H-T14
  ROLE: Supports
- TYPE: Parent
  VALUE: H-T15
  ROLE: Supports
- TYPE: Parent
  VALUE: H-T16
  ROLE: Supports
- TYPE: Parent
  VALUE: H-T17
  ROLE: Supports
- TYPE: Parent
  VALUE: H-T18
  ROLE: Supports
- TYPE: Parent
  VALUE: H-T19
  ROLE: Supports
- TYPE: Parent
  VALUE: H-T20
  ROLE: Supports
- TYPE: Parent
  VALUE: H-T21
  ROLE: Supports
- TYPE: Parent
  VALUE: H-T22
  ROLE: Supports
- TYPE: Parent
  VALUE: H-T23
  ROLE: Supports
- TYPE: Parent
  VALUE: H-T24
  ROLE: Supports
