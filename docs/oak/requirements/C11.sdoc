[DOCUMENT]
TITLE: C11: Human interface
UID: OAK-C11
VERSION: 0.4.4

[GRAMMAR]
IMPORT_FROM_FILE: oak.sgra

[COMPONENT]
UID: C11
STATUS: Proposed
OWNER: C11
SOURCE: docs/oak/implementation/C11-interface.md
SCOPE: Production
VERIFICATION: NotRun
TITLE: Human interface
STATEMENT: >>>
Provide project and agent navigation plus distinct schema, evidence, dependency, and execution views.
<<<
RELATIONS:
- TYPE: Parent
  VALUE: OAK
  ROLE: OwnedBy

[REQUIREMENT]
UID: C11-R01
STATUS: Proposed
OWNER: C11
SOURCE: docs/oak/implementation/C11-interface.md
SCOPE: Production
VERIFICATION: NotRun
TITLE: C11 must load the current session before it requests project data.
STATEMENT: >>>
C11 must load the current session before it requests project data.
<<<
RELATIONS:
- TYPE: Parent
  VALUE: C11
  ROLE: OwnedBy
- TYPE: Parent
  VALUE: CT-C11
  ROLE: ConstrainedBy

[REQUIREMENT]
UID: C11-R02
STATUS: Proposed
OWNER: C11
SOURCE: docs/oak/implementation/C11-interface.md
SCOPE: Production
VERIFICATION: NotRun
TITLE: C11 must include project and agent scope in every applicable request and cache key.
STATEMENT: >>>
C11 must include project and agent scope in every applicable request and cache key.
<<<
RELATIONS:
- TYPE: Parent
  VALUE: C11
  ROLE: OwnedBy
- TYPE: Parent
  VALUE: CT-C11
  ROLE: ConstrainedBy
- TYPE: Parent
  VALUE: CT-C9
  ROLE: Consumes

[REQUIREMENT]
UID: C11-R03
STATUS: Proposed
OWNER: C11
SOURCE: docs/oak/implementation/C11-interface.md
SCOPE: Production
VERIFICATION: NotRun
TITLE: C11 must display the package and evidence revision used by each result.
STATEMENT: >>>
C11 must display the package and evidence revision used by each result.
<<<
RELATIONS:
- TYPE: Parent
  VALUE: C11
  ROLE: OwnedBy
- TYPE: Parent
  VALUE: CT-C11
  ROLE: ConstrainedBy
- TYPE: Parent
  VALUE: CT-C7
  ROLE: Consumes
- TYPE: Parent
  VALUE: CT-PACKAGE
  ROLE: Consumes

[REQUIREMENT]
UID: C11-R04
STATUS: Proposed
OWNER: C11
SOURCE: docs/oak/implementation/C11-interface.md
SCOPE: Production
VERIFICATION: NotRun
TITLE: C11 must keep schema, facts, dependencies, and execution views separate.
STATEMENT: >>>
C11 must keep schema, facts, dependencies, and execution views separate.
<<<
RELATIONS:
- TYPE: Parent
  VALUE: C11
  ROLE: OwnedBy
- TYPE: Parent
  VALUE: CT-C11
  ROLE: ConstrainedBy

[REQUIREMENT]
UID: C11-R05
STATUS: Proposed
OWNER: C11
SOURCE: docs/oak/implementation/C11-interface.md
SCOPE: Production
VERIFICATION: NotRun
TITLE: C11 must expose source references and consumers for each displayed requirement.
STATEMENT: >>>
C11 must expose source references and consumers for each displayed requirement.
<<<
RELATIONS:
- TYPE: Parent
  VALUE: C11
  ROLE: OwnedBy
- TYPE: Parent
  VALUE: CT-C11
  ROLE: ConstrainedBy

[REQUIREMENT]
UID: C11-R06
STATUS: Proposed
OWNER: C11
SOURCE: docs/oak/implementation/C11-interface.md
SCOPE: Production
VERIFICATION: NotRun
TITLE: C11 must retain unknown, conflicting, stale, unsupported, and unrun states.
STATEMENT: >>>
C11 must retain unknown, conflicting, stale, unsupported, and unrun states.
<<<
RELATIONS:
- TYPE: Parent
  VALUE: C11
  ROLE: OwnedBy
- TYPE: Parent
  VALUE: CT-C11
  ROLE: ConstrainedBy

[REQUIREMENT]
UID: C11-R07
STATUS: Proposed
OWNER: C11
SOURCE: docs/oak/implementation/C11-interface.md
SCOPE: Production
VERIFICATION: NotRun
TITLE: C11 must create candidates through C10 instead of modifying active artifacts.
STATEMENT: >>>
C11 must create candidates through C10 instead of modifying active artifacts.
<<<
RELATIONS:
- TYPE: Parent
  VALUE: C11
  ROLE: OwnedBy
- TYPE: Parent
  VALUE: CT-C11
  ROLE: ConstrainedBy

[REQUIREMENT]
UID: C11-R08
STATUS: Proposed
OWNER: C11
SOURCE: docs/oak/implementation/C11-interface.md
SCOPE: Production
VERIFICATION: NotRun
TITLE: C11 must submit reviewed hashes when it requests approval or activation.
STATEMENT: >>>
C11 must submit reviewed hashes when it requests approval or activation.
<<<
RELATIONS:
- TYPE: Parent
  VALUE: C11
  ROLE: OwnedBy
- TYPE: Parent
  VALUE: CT-C11
  ROLE: ConstrainedBy
- TYPE: Parent
  VALUE: CT-C6
  ROLE: Consumes

[REQUIREMENT]
UID: C11-R09
STATUS: Proposed
OWNER: C11
SOURCE: docs/oak/implementation/C11-interface.md
SCOPE: Production
VERIFICATION: NotRun
TITLE: C11 must wait for the authoritative activation response before it changes the active-versi
STATEMENT: >>>
C11 must wait for the authoritative activation response before it changes the active-version display.
<<<
RELATIONS:
- TYPE: Parent
  VALUE: C11
  ROLE: OwnedBy
- TYPE: Parent
  VALUE: CT-C11
  ROLE: ConstrainedBy

[REQUIREMENT]
UID: C11-R10
STATUS: Proposed
OWNER: C11
SOURCE: docs/oak/implementation/C11-interface.md
SCOPE: Production
VERIFICATION: NotRun
TITLE: C11 must discard delayed responses whose view binding differs from the selected binding.
STATEMENT: >>>
C11 must discard delayed responses whose view binding differs from the selected binding.
<<<
RELATIONS:
- TYPE: Parent
  VALUE: C11
  ROLE: OwnedBy
- TYPE: Parent
  VALUE: CT-C11
  ROLE: ConstrainedBy

[REQUIREMENT]
UID: C11-R11
STATUS: Proposed
OWNER: C11
SOURCE: docs/oak/implementation/C11-interface.md
SCOPE: Production
VERIFICATION: NotRun
TITLE: C11 must clear sensitive state after logout, session expiry, or scope revocation.
STATEMENT: >>>
C11 must clear sensitive state after logout, session expiry, or scope revocation.
<<<
RELATIONS:
- TYPE: Parent
  VALUE: C11
  ROLE: OwnedBy
- TYPE: Parent
  VALUE: CT-C11
  ROLE: ConstrainedBy

[REQUIREMENT]
UID: C11-R12
STATUS: Proposed
OWNER: C11
SOURCE: docs/oak/implementation/C11-interface.md
SCOPE: Production
VERIFICATION: NotRun
TITLE: C11 must provide a keyboard-accessible table for every graph view.
STATEMENT: >>>
C11 must provide a keyboard-accessible table for every graph view.
<<<
RELATIONS:
- TYPE: Parent
  VALUE: C11
  ROLE: OwnedBy
- TYPE: Parent
  VALUE: CT-C11
  ROLE: ConstrainedBy

[REQUIREMENT]
UID: C11-R13
STATUS: Proposed
OWNER: C11
SOURCE: docs/oak/implementation/C11-interface.md
SCOPE: Production
VERIFICATION: NotRun
TITLE: C11 must label truncation and require explicit expansion before it requests more graph dat
STATEMENT: >>>
C11 must label truncation and require explicit expansion before it requests more graph data.
<<<
RELATIONS:
- TYPE: Parent
  VALUE: C11
  ROLE: OwnedBy
- TYPE: Parent
  VALUE: CT-C11
  ROLE: ConstrainedBy

[REQUIREMENT]
UID: C11-R14
STATUS: Proposed
OWNER: C11
SOURCE: docs/oak/implementation/C11-interface.md
SCOPE: Production
VERIFICATION: NotRun
TITLE: C11 must keep credentials and evaluator-private material outside browser payloads and stor
STATEMENT: >>>
C11 must keep credentials and evaluator-private material outside browser payloads and storage.
<<<
RELATIONS:
- TYPE: Parent
  VALUE: C11
  ROLE: OwnedBy
- TYPE: Parent
  VALUE: CT-C11
  ROLE: ConstrainedBy

[REQUIREMENT]
UID: C11-R15
STATUS: Proposed
OWNER: C11
SOURCE: docs/oak/implementation/C11-interface.md
SCOPE: Production
VERIFICATION: NotRun
TITLE: C11 must show the execution mode and admitted budget before a run or verification command.
STATEMENT: >>>
C11 must show the execution mode and admitted budget before a run or verification command.
<<<
RELATIONS:
- TYPE: Parent
  VALUE: C11
  ROLE: OwnedBy
- TYPE: Parent
  VALUE: CT-C11
  ROLE: ConstrainedBy
- TYPE: Parent
  VALUE: CT-C8
  ROLE: Consumes

[REQUIREMENT]
UID: C11-R16
STATUS: Proposed
OWNER: C11
SOURCE: docs/oak/implementation/C11-interface.md
SCOPE: Production
VERIFICATION: NotRun
TITLE: C11 must display the resolved loop shape and distinguish configuration, binding, admission
STATEMENT: >>>
C11 must display the resolved loop shape and distinguish configuration, binding, admission, verification, and mount evidence.
<<<
RELATIONS:
- TYPE: Parent
  VALUE: C11
  ROLE: OwnedBy
- TYPE: Parent
  VALUE: CT-C11
  ROLE: ConstrainedBy
- TYPE: Parent
  VALUE: CT-AGENT-SHAPE
  ROLE: Consumes
- TYPE: Parent
  VALUE: CT-C8
  ROLE: Consumes
- TYPE: Parent
  VALUE: CT-C9
  ROLE: Consumes

[REQUIREMENT]
UID: C11-R17
STATUS: Proposed
OWNER: C11
SOURCE: docs/oak/implementation/C11-interface.md
SCOPE: Production
VERIFICATION: NotRun
TITLE: C11 must show separate verification gates and paired results for every assigned case, including
STATEMENT: >>>
C11 must show separate verification gates and paired results for every assigned case, including protected prior passes.
<<<
RELATIONS:
- TYPE: Parent
  VALUE: C11
  ROLE: OwnedBy
- TYPE: Parent
  VALUE: CT-C11
  ROLE: ConstrainedBy
- TYPE: Parent
  VALUE: CT-C6
  ROLE: Consumes

[REQUIREMENT]
UID: C11-R18
STATUS: Proposed
OWNER: C11
SOURCE: docs/oak/implementation/C11-interface.md
SCOPE: Production
VERIFICATION: NotRun
TITLE: C11 must keep activation unavailable when C6 reports an unintended regression or incomplete requ
STATEMENT: >>>
C11 must keep activation unavailable when C6 reports an unintended regression or incomplete required comparison, even if OWL verification passes.
<<<
RELATIONS:
- TYPE: Parent
  VALUE: C11
  ROLE: OwnedBy
- TYPE: Parent
  VALUE: CT-C11
  ROLE: ConstrainedBy
- TYPE: Parent
  VALUE: CT-C6
  ROLE: Consumes

[REQUIREMENT]
UID: C11-R19
STATUS: Proposed
OWNER: C11
SOURCE: docs/oak/implementation/C11-interface.md
SCOPE: Production
VERIFICATION: NotRun
TITLE: Display frozen selection policy and coverage by versioned task characteristics
STATEMENT: >>>
C11 must display the frozen selection policy before verification and show coverage by versioned task characteristics with the full unique-case denominator.
<<<
RELATIONS:
- TYPE: Parent
  VALUE: C11
  ROLE: OwnedBy
- TYPE: Parent
  VALUE: CT-C11
  ROLE: ConstrainedBy
- TYPE: Parent
  VALUE: CT-C6
  ROLE: Consumes

[REQUIREMENT]
UID: C11-R20
STATUS: Proposed
OWNER: C11
SOURCE: docs/oak/implementation/C11-interface.md
SCOPE: Production
VERIFICATION: NotRun
TITLE: Preserve required coverage and block missing required groups or mandatory cases
STATEMENT: >>>
C11 must preserve required coverage under filters and keep activation unavailable when C6 reports a missing required group or mandatory case.
<<<
RELATIONS:
- TYPE: Parent
  VALUE: C11
  ROLE: OwnedBy
- TYPE: Parent
  VALUE: CT-C11
  ROLE: ConstrainedBy
- TYPE: Parent
  VALUE: CT-C6
  ROLE: Consumes

[TEST]
UID: C11-T01
STATUS: Specified
OWNER: C11
SOURCE: docs/oak/implementation/C11-interface.md
SCOPE: Production
VERIFICATION: NotRun
TITLE: Login, create project, create preset agent, admit replay
STATEMENT: >>>
Input or fault: Login, create project, create preset agent, admit replay.
Expected observation: Correct scoped references; no private evaluator reference or manual artifact-ID requirement.
<<<
RATIONALE: >>>
This link records a planned verification obligation. It does not establish execution or complete coverage.
<<<
RELATIONS:
- TYPE: Parent
  VALUE: C11
  ROLE: OwnedBy
- TYPE: Parent
  VALUE: CT-C11
  ROLE: ConstrainedBy
- TYPE: Parent
  VALUE: C11-R01
  ROLE: Verifies

[TEST]
UID: C11-T02
STATUS: Specified
OWNER: C11
SOURCE: docs/oak/implementation/C11-interface.md
SCOPE: Production
VERIFICATION: NotRun
TITLE: Viewer opens editor or activation route directly
STATEMENT: >>>
Input or fault: Viewer opens editor or activation route directly.
Expected observation: Read-only view or denial; server receives no authorized mutation.
<<<
RATIONALE: >>>
This link records a planned verification obligation. It does not establish execution or complete coverage.
<<<
RELATIONS:
- TYPE: Parent
  VALUE: C11
  ROLE: OwnedBy
- TYPE: Parent
  VALUE: CT-C11
  ROLE: ConstrainedBy
- TYPE: Parent
  VALUE: C11-R02
  ROLE: Verifies

[TEST]
UID: C11-T03
STATUS: Specified
OWNER: C11
SOURCE: docs/oak/implementation/C11-interface.md
SCOPE: Production
VERIFICATION: NotRun
TITLE: Navigate between projects while old requests finish
STATEMENT: >>>
Input or fault: Navigate between projects while old requests finish.
Expected observation: No old-project data appears in the new view.
<<<
RATIONALE: >>>
This link records a planned verification obligation. It does not establish execution or complete coverage.
<<<
RELATIONS:
- TYPE: Parent
  VALUE: C11
  ROLE: OwnedBy
- TYPE: Parent
  VALUE: CT-C11
  ROLE: ConstrainedBy
- TYPE: Parent
  VALUE: C11-R02
  ROLE: Verifies
- TYPE: Parent
  VALUE: C11-R10
  ROLE: Verifies

[TEST]
UID: C11-T04
STATUS: Specified
OWNER: C11
SOURCE: docs/oak/implementation/C11-interface.md
SCOPE: Production
VERIFICATION: NotRun
TITLE: View source fixture before projection or function execution
STATEMENT: >>>
Input or fault: View source fixture before projection or function execution.
Expected observation: Source values appear; graph and test statuses remain unrun.
<<<
RATIONALE: >>>
This link records a planned verification obligation. It does not establish execution or complete coverage.
<<<
RELATIONS:
- TYPE: Parent
  VALUE: C11
  ROLE: OwnedBy
- TYPE: Parent
  VALUE: CT-C11
  ROLE: ConstrainedBy
- TYPE: Parent
  VALUE: C11-R06
  ROLE: Verifies

[TEST]
UID: C11-T05
STATUS: Specified
OWNER: C11
SOURCE: docs/oak/implementation/C11-interface.md
SCOPE: Production
VERIFICATION: NotRun
TITLE: Unknown, conflict, false, stale, and unsupported values
STATEMENT: >>>
Input or fault: Unknown, conflict, false, stale, and unsupported values.
Expected observation: Distinct text labels and causes; none becomes an implicit pass.
<<<
RATIONALE: >>>
This link records a planned verification obligation. It does not establish execution or complete coverage.
<<<
RELATIONS:
- TYPE: Parent
  VALUE: C11
  ROLE: OwnedBy
- TYPE: Parent
  VALUE: CT-C11
  ROLE: ConstrainedBy
- TYPE: Parent
  VALUE: C11-R06
  ROLE: Verifies

[TEST]
UID: C11-T06
STATUS: Specified
OWNER: C11
SOURCE: docs/oak/implementation/C11-interface.md
SCOPE: Production
VERIFICATION: NotRun
TITLE: Inspect a property, assertion, function, and failure
STATEMENT: >>>
Input or fault: Inspect a property, assertion, function, and failure.
Expected observation: Correct version, source, dependency, and operation references.
<<<
RATIONALE: >>>
This link records a planned verification obligation. It does not establish execution or complete coverage.
<<<
RELATIONS:
- TYPE: Parent
  VALUE: C11
  ROLE: OwnedBy
- TYPE: Parent
  VALUE: CT-C11
  ROLE: ConstrainedBy
- TYPE: Parent
  VALUE: C11-R03
  ROLE: Verifies
- TYPE: Parent
  VALUE: C11-R04
  ROLE: Verifies
- TYPE: Parent
  VALUE: C11-R05
  ROLE: Verifies

[TEST]
UID: C11-T07
STATUS: Specified
OWNER: C11
SOURCE: docs/oak/implementation/C11-interface.md
SCOPE: Production
VERIFICATION: NotRun
TITLE: Open facts with an incompatible package or revision
STATEMENT: >>>
Input or fault: Open facts with an incompatible package or revision.
Expected observation: No combined verified view; mismatch remains visible.
<<<
RATIONALE: >>>
This link records a planned verification obligation. It does not establish execution or complete coverage.
<<<
RELATIONS:
- TYPE: Parent
  VALUE: C11
  ROLE: OwnedBy
- TYPE: Parent
  VALUE: CT-C11
  ROLE: ConstrainedBy
- TYPE: Parent
  VALUE: C11-R03
  ROLE: Verifies
- TYPE: Parent
  VALUE: C11-R10
  ROLE: Verifies

[TEST]
UID: C11-T08
STATUS: Specified
OWNER: C11
SOURCE: docs/oak/implementation/C11-interface.md
SCOPE: Production
VERIFICATION: NotRun
TITLE: Propose a schema change and move canvas nodes
STATEMENT: >>>
Input or fault: Propose a schema change and move canvas nodes.
Expected observation: Only candidate command submitted; active schema and facts remain unchanged.
<<<
RATIONALE: >>>
This link records a planned verification obligation. It does not establish execution or complete coverage.
<<<
RELATIONS:
- TYPE: Parent
  VALUE: C11
  ROLE: OwnedBy
- TYPE: Parent
  VALUE: CT-C11
  ROLE: ConstrainedBy
- TYPE: Parent
  VALUE: C11-R07
  ROLE: Verifies

[TEST]
UID: C11-T09
STATUS: Specified
OWNER: C11
SOURCE: docs/oak/implementation/C11-interface.md
SCOPE: Production
VERIFICATION: NotRun
TITLE: Verification fails, times out, or lacks a gate
STATEMENT: >>>
Input or fault: Verification fails, times out, or lacks a gate.
Expected observation: Separate non-pass states; activation remains unavailable.
<<<
RATIONALE: >>>
This link records a planned verification obligation. It does not establish execution or complete coverage.
<<<
RELATIONS:
- TYPE: Parent
  VALUE: C11
  ROLE: OwnedBy
- TYPE: Parent
  VALUE: CT-C11
  ROLE: ConstrainedBy
- TYPE: Parent
  VALUE: C11-R06
  ROLE: Verifies
- TYPE: Parent
  VALUE: C6-R07
  ROLE: Verifies

[TEST]
UID: C11-T10
STATUS: Specified
OWNER: C11
SOURCE: docs/oak/implementation/C11-interface.md
SCOPE: Production
VERIFICATION: NotRun
TITLE: Candidate or base changes after approval
STATEMENT: >>>
Input or fault: Candidate or base changes after approval.
Expected observation: 409; no optimistic activation or reused approval.
<<<
RATIONALE: >>>
This link records a planned verification obligation. It does not establish execution or complete coverage.
<<<
RELATIONS:
- TYPE: Parent
  VALUE: C11
  ROLE: OwnedBy
- TYPE: Parent
  VALUE: CT-C11
  ROLE: ConstrainedBy
- TYPE: Parent
  VALUE: C11-R08
  ROLE: Verifies
- TYPE: Parent
  VALUE: C11-R09
  ROLE: Verifies
- TYPE: Parent
  VALUE: C6-R08
  ROLE: Verifies

[TEST]
UID: C11-T11
STATUS: Specified
OWNER: C11
SOURCE: docs/oak/implementation/C11-interface.md
SCOPE: Production
VERIFICATION: NotRun
TITLE: Repeat submission after response loss
STATEMENT: >>>
Input or fault: Repeat submission after response loss.
Expected observation: Same key and body; one saved command and one displayed result.
<<<
RATIONALE: >>>
This link records a planned verification obligation. It does not establish execution or complete coverage.
<<<
RELATIONS:
- TYPE: Parent
  VALUE: C11
  ROLE: OwnedBy
- TYPE: Parent
  VALUE: CT-C11
  ROLE: ConstrainedBy

[TEST]
UID: C11-T12
STATUS: Specified
OWNER: C11
SOURCE: docs/oak/implementation/C11-interface.md
SCOPE: Production
VERIFICATION: NotRun
TITLE: Logout or membership revocation during polling
STATEMENT: >>>
Input or fault: Logout or membership revocation during polling.
Expected observation: Polling stops; protected caches and inspectors clear.
<<<
RATIONALE: >>>
This link records a planned verification obligation. It does not establish execution or complete coverage.
<<<
RELATIONS:
- TYPE: Parent
  VALUE: C11
  ROLE: OwnedBy
- TYPE: Parent
  VALUE: CT-C11
  ROLE: ConstrainedBy
- TYPE: Parent
  VALUE: C11-R11
  ROLE: Verifies

[TEST]
UID: C11-T13
STATUS: Specified
OWNER: C11
SOURCE: docs/oak/implementation/C11-interface.md
SCOPE: Production
VERIFICATION: NotRun
TITLE: Graph exceeds its requested bounds
STATEMENT: >>>
Input or fault: Graph exceeds its requested bounds.
Expected observation: Truncation shown; explicit bounded expansion or paginated table.
<<<
RATIONALE: >>>
This link records a planned verification obligation. It does not establish execution or complete coverage.
<<<
RELATIONS:
- TYPE: Parent
  VALUE: C11
  ROLE: OwnedBy
- TYPE: Parent
  VALUE: CT-C11
  ROLE: ConstrainedBy
- TYPE: Parent
  VALUE: C11-R13
  ROLE: Verifies

[TEST]
UID: C11-T14
STATUS: Specified
OWNER: C11
SOURCE: docs/oak/implementation/C11-interface.md
SCOPE: Production
VERIFICATION: NotRun
TITLE: Keyboard and screen-reader inspection
STATEMENT: >>>
Input or fault: Keyboard and screen-reader inspection.
Expected observation: Graph/table parity, named controls, focus restoration, no color-only information.
<<<
RATIONALE: >>>
This link records a planned verification obligation. It does not establish execution or complete coverage.
<<<
RELATIONS:
- TYPE: Parent
  VALUE: C11
  ROLE: OwnedBy
- TYPE: Parent
  VALUE: CT-C11
  ROLE: ConstrainedBy
- TYPE: Parent
  VALUE: C11-R12
  ROLE: Verifies

[TEST]
UID: C11-T15
STATUS: Specified
OWNER: C11
SOURCE: docs/oak/implementation/C11-interface.md
SCOPE: Production
VERIFICATION: NotRun
TITLE: Raw HTML, evaluator canary, or credential enters a response
STATEMENT: >>>
Input or fault: Raw HTML, evaluator canary, or credential enters a response.
Expected observation: Text rendering or boundary rejection; no executable markup or secret persistence.
<<<
RATIONALE: >>>
This link records a planned verification obligation. It does not establish execution or complete coverage.
<<<
RELATIONS:
- TYPE: Parent
  VALUE: C11
  ROLE: OwnedBy
- TYPE: Parent
  VALUE: CT-C11
  ROLE: ConstrainedBy
- TYPE: Parent
  VALUE: C11-R14
  ROLE: Verifies

[TEST]
UID: C11-T16
STATUS: Specified
OWNER: C11
SOURCE: docs/oak/implementation/C11-interface.md
SCOPE: Production
VERIFICATION: NotRun
TITLE: Show replay result and operation totals
STATEMENT: >>>
Input or fault: Show replay result and operation totals.
Expected observation: Synthetic status, pinned versions, partial coverage, and separate operation categories remain visible.
<<<
RATIONALE: >>>
This link records a planned verification obligation. It does not establish execution or complete coverage.
<<<
RELATIONS:
- TYPE: Parent
  VALUE: C11
  ROLE: OwnedBy
- TYPE: Parent
  VALUE: CT-C11
  ROLE: ConstrainedBy
- TYPE: Parent
  VALUE: C11-R03
  ROLE: Verifies
- TYPE: Parent
  VALUE: C11-R15
  ROLE: Verifies

[TEST]
UID: C11-T17
STATUS: Specified
OWNER: C11
SOURCE: docs/oak/implementation/C11-interface.md
SCOPE: Production
VERIFICATION: NotRun
TITLE: Create a preset while registry probes are queued or failed
STATEMENT: >>>
Input or fault: Create a preset while registry probes are queued or failed.
Expected observation: Display resolved shape and distinct evidence stages; never show configuration creation as run readiness.
<<<
RATIONALE: >>>
This link records a planned verification obligation. It does not establish execution or complete coverage.
<<<
RELATIONS:
- TYPE: Parent
  VALUE: C11
  ROLE: OwnedBy
- TYPE: Parent
  VALUE: CT-C11
  ROLE: ConstrainedBy
- TYPE: Parent
  VALUE: C11-R16
  ROLE: Verifies

[TEST]
UID: C11-T18
STATUS: Specified
OWNER: C11
SOURCE: docs/oak/implementation/C11-interface.md
SCOPE: Production
VERIFICATION: NotRun
TITLE: Inspect a sealed verification set and a candidate-verification run
STATEMENT: >>>
Input or fault: Inspect a sealed verification set and a candidate-verification run.
Expected observation: Approval uses the returned set hash; run purpose and denominator stay separate from ordinary evaluation.
<<<
RATIONALE: >>>
This link records a planned verification obligation. It does not establish execution or complete coverage.
<<<
RELATIONS:
- TYPE: Parent
  VALUE: C11
  ROLE: OwnedBy
- TYPE: Parent
  VALUE: CT-C11
  ROLE: ConstrainedBy
- TYPE: Parent
  VALUE: C11-R08
  ROLE: Verifies
- TYPE: Parent
  VALUE: C11-R16
  ROLE: Verifies

[TEST]
UID: C11-T19
STATUS: Specified
OWNER: C11
SOURCE: docs/oak/implementation/C11-interface.md
SCOPE: Production
VERIFICATION: NotRun
TITLE: HermiT passes but a protected previously passing case fails under the candidate
STATEMENT: >>>
Input or fault: HermiT passes but a protected previously passing case fails under the candidate.
Expected observation: Separate logic pass and regression failure; activation remains unavailable and the active package stays unchanged.
<<<
RELATIONS:
- TYPE: Parent
  VALUE: C11
  ROLE: OwnedBy
- TYPE: Parent
  VALUE: CT-C11
  ROLE: ConstrainedBy
- TYPE: Parent
  VALUE: C11-R17
  ROLE: Verifies
- TYPE: Parent
  VALUE: C11-R18
  ROLE: Verifies
- TYPE: Parent
  VALUE: C11-R09
  ROLE: Verifies

[TEST]
UID: C11-T20
STATUS: Specified
OWNER: C11
SOURCE: docs/oak/implementation/C11-interface.md
SCOPE: Production
VERIFICATION: NotRun
TITLE: A protected case is missing, timed out, or not run while the result table is filtered
STATEMENT: >>>
Input or fault: A protected case is missing, timed out, or not run while the result table is filtered.
Expected observation: Full assigned and protected denominators remain visible; incomplete cases remain listed and activation stays unavailable.
<<<
RELATIONS:
- TYPE: Parent
  VALUE: C11
  ROLE: OwnedBy
- TYPE: Parent
  VALUE: CT-C11
  ROLE: ConstrainedBy
- TYPE: Parent
  VALUE: C11-R17
  ROLE: Verifies
- TYPE: Parent
  VALUE: C11-R18
  ROLE: Verifies
- TYPE: Parent
  VALUE: C11-R06
  ROLE: Verifies

[TEST]
UID: C11-T21
STATUS: Specified
OWNER: C11
SOURCE: docs/oak/implementation/C11-interface.md
SCOPE: Production
VERIFICATION: NotRun
TITLE: Inspect a schema term and its function, then suggest a supported behavior change
STATEMENT: >>>
Input or fault: Inspect a schema term and its function, then suggest a supported behavior change.
Expected observation: Stable task and artifact references reach the candidate; the proposal diff, affected cases, and separate verification gates are visible.
<<<
RELATIONS:
- TYPE: Parent
  VALUE: C11
  ROLE: OwnedBy
- TYPE: Parent
  VALUE: CT-C11
  ROLE: ConstrainedBy
- TYPE: Parent
  VALUE: C11-R05
  ROLE: Verifies
- TYPE: Parent
  VALUE: C11-R07
  ROLE: Verifies
- TYPE: Parent
  VALUE: C11-R17
  ROLE: Verifies

[TEST]
UID: C11-T22
STATUS: Specified
OWNER: C11
SOURCE: docs/oak/implementation/C11-interface.md
SCOPE: Production
VERIFICATION: NotRun
TITLE: Inspect the selection before Verify, then retry after a candidate failure
STATEMENT: >>>
Input or fault: Inspect the selection before Verify, then retry after a candidate failure.
Expected observation: Snapshot, characteristic versions, policy, seed, required groups, case IDs, and planned budget remain visible; retry cannot resample away failures.
<<<
RELATIONS:
- TYPE: Parent
  VALUE: C11
  ROLE: OwnedBy
- TYPE: Parent
  VALUE: CT-C11
  ROLE: ConstrainedBy
- TYPE: Parent
  VALUE: C11-R19
  ROLE: Verifies
- TYPE: Parent
  VALUE: C11-R15
  ROLE: Verifies

[TEST]
UID: C11-T23
STATUS: Specified
OWNER: C11
SOURCE: docs/oak/implementation/C11-interface.md
SCOPE: Production
VERIFICATION: NotRun
TITLE: Filter coverage with overlapping tags and absent or unknown target distribution
STATEMENT: >>>
Input or fault: A case has overlapping tags and selection reasons while a schema or function filter is active and the target distribution is absent or unknown.
Expected observation: Full unique-case total stays fixed, repetitions are separate, routine and challenge outcomes stay distinct, and coverage_only appears without a representative-success score.
<<<
RELATIONS:
- TYPE: Parent
  VALUE: C11
  ROLE: OwnedBy
- TYPE: Parent
  VALUE: CT-C11
  ROLE: ConstrainedBy
- TYPE: Parent
  VALUE: C11-R19
  ROLE: Verifies
- TYPE: Parent
  VALUE: C11-R20
  ROLE: Verifies

[TEST]
UID: C11-T24
STATUS: Specified
OWNER: C11
SOURCE: docs/oak/implementation/C11-interface.md
SCOPE: Production
VERIFICATION: NotRun
TITLE: Executed cases pass while required coverage remains incomplete
STATEMENT: >>>
Input or fault: All executed cases pass but a required group is underfilled or a mandatory case is missing.
Expected observation: Coverage gaps remain visible and activation stays unavailable despite passing OWL and executed-case results.
<<<
RELATIONS:
- TYPE: Parent
  VALUE: C11
  ROLE: OwnedBy
- TYPE: Parent
  VALUE: CT-C11
  ROLE: ConstrainedBy
- TYPE: Parent
  VALUE: C11-R20
  ROLE: Verifies
- TYPE: Parent
  VALUE: C11-R18
  ROLE: Verifies
